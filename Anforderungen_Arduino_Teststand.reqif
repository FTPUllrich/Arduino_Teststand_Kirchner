# Mikrocontroller-Teststand Lastenheft
System-Anforderungsspezifikation (VDI 2206 / VDI 2221) nach Schulcheckliste

# Specification: Systemanforderungen Arduino Teststand
- Dokumententitel: Mikrocontroller-Teststand zur analogen Messwerterfassung (VDI 2206)

## so_A01: A-01
- Kategorie: Sensorik & Erfassung
- Titel: Analoge Eingangserfassung
- Spezifikation: Kontinuierliche Erfassung eines analogen DC-Signals (0..5,00 V) ueber 10-Bit-Quantisierung (0..1023 Digits) an Analogeingang A0.
- Zielwert / Akzeptanzkriterium: Linearitaetsfehler <= +-2 LSB
- Verifikationsmethode: Kalibrierte DC-Spannungsquelle & Digitalmultimeter (DMM)
- Klassifizierung: Festforderung
- Prioritaet: Hoch

## so_A02: A-02
- Kategorie: Signalverarbeitung
- Titel: Rauschunterdrueckung & Glaettung
- Spezifikation: Zeitdiskrete Glaettung des Eingangssignals mittels gleitendem arithmetischem Mittelwert ueber genau N=10 aufeinanderfolgende Messpunkte.
- Zielwert / Akzeptanzkriterium: Abtastintervall dt=50ms +- 2ms (20 Hz Abtastrate)
- Verifikationsmethode: Signalvergleich Roh- vs. Filterwert im Serial Plotter
- Klassifizierung: Festforderung
- Prioritaet: Hoch

## so_A03: A-03
- Kategorie: Systemskalierung
- Titel: Erweiterbarkeit der Eingangskanaele
- Spezifikation: Systemarchitektur muss fuer die synchrone Erfassung von bis zu 6 analogen Signalgebern modular erweiterbar sein.
- Zielwert / Akzeptanzkriterium: Hard- und Softwaredesign unterstuetzt A0..A5
- Verifikationsmethode: Funktionstest mit bis zu 6 analogen Signalgebern
- Klassifizierung: Wunschforderung
- Prioritaet: Mittel

## so_A04: A-04
- Kategorie: Kommunikation
- Titel: Zyklische Bus-Datenuebertragung
- Spezifikation: Unaufgeforderte, zyklische Uebertragung des berechneten Messwerts und des Rohwerts ueber eine serielle Punkt-zu-Punkt-Busverbindung.
- Zielwert / Akzeptanzkriterium: Uebertragungsrate f_bus >= 10 Hz (Intervall <= 100ms), 9600 Baud 8N1, Telegramm <VAL:xxxx;RAW:xxxx>
- Verifikationsmethode: Logikanalysator / Serial-Monitor-Trace mit Zeitstempeln
- Klassifizierung: Festforderung
- Prioritaet: Hoch

## so_A05: A-05
- Kategorie: Systemrobustheit
- Titel: Bus-Timeout & Verbindungsueberwachung
- Spezifikation: Selbststaendige Erkennung eines Kommunikationsausfalls mit optischer Warnanzeige und automatischem Wiederanlauf bei Signalrueckkehr.
- Zielwert / Akzeptanzkriterium: Wechsel in Fehlermodus bei Ausfall > 2.0 s; Wiederanlaufzeit <= 200 ms
- Verifikationsmethode: Unterbrechung der RX/TX-Signalleitung im laufenden Betrieb
- Klassifizierung: Festforderung
- Prioritaet: Hoch

## so_A06: A-06
- Kategorie: HMI / Display
- Titel: Messwert-Visualisierung
- Spezifikation: Strukturierte 4-zeilige Monospace-Textanzeige zur simultanen Darstellung von Binaerwert, Dezimalwert, Abweichung und Systemstatus.
- Zielwert / Akzeptanzkriterium: 4 Zeilen a 20 Zeichen, serielle 2-Draht-Ansteuerung (100 kHz Busfrequenz)
- Verifikationsmethode: I2C-Bus-Scan / Hardwaretest mit Oszilloskop
- Klassifizierung: Festforderung
- Prioritaet: Hoch

## so_A07: A-07
- Kategorie: HMI / Format
- Titel: Binaere Messwertdarstellung
- Spezifikation: Formatierte 10-Bit-Binaerausgabe mit fuehrenden Nullen und optischer 4-Bit-Nibble-Trennung auf Zeile 1 des Displays.
- Zielwert / Akzeptanzkriterium: Formatierung exakt BIN: bb bbbb bbbb ueber vollen Bereich (0..1023)
- Verifikationsmethode: Sichtpruefung der LCD-Anzeige ueber gesamten Stellbereich
- Klassifizierung: Festforderung
- Prioritaet: Mittel

## so_A08: A-08
- Kategorie: HMI / Bedienung
- Titel: Messwert-Uebernahme (Hold-Funktion)
- Spezifikation: Aktualisierung der Displayanzeige ausschliesslich bei gezielter Betaetigung des Bedientasters; dauerhaftes Halten des Anzeigewerts bis zum Folgeimpuls.
- Zielwert / Akzeptanzkriterium: Sichere Unterdrueckung von Kontaktprellen mit Entprellzeit t_deb >= 50 ms
- Verifikationsmethode: Prellpruefung / Funktionstest mit Oszilloskop am Tastereingang
- Klassifizierung: Festforderung
- Prioritaet: Hoch

## so_A09: A-09
- Kategorie: Systemdynamik
- Titel: Reaktionszeit HMI-Aktualisierung
- Spezifikation: Zeitverzoegerung zwischen Tasterbetaetigung (fallende Flanke) und vollstaendiger Aktualisierung des Displayinhalts.
- Zielwert / Akzeptanzkriterium: Gesamtlatenzzeit t_lat <= 100 ms
- Verifikationsmethode: 2-Kanal-Oszilloskop (Trigger Flanke Taster -> I2C Paket)
- Klassifizierung: Festforderung
- Prioritaet: Mittel

## so_A10: A-10
- Kategorie: Systemstart
- Titel: Definiertes Initialisierungsverhalten
- Spezifikation: Deterministischer Kaltstart-Ablauf mit Begruessungsanzeige, Filter-Vorbefuellung und Einnahme eines sicheren Wartezustands.
- Zielwert / Akzeptanzkriterium: Boot-Screen 2.0 s +- 0.1 s, Vorbefuellung N=10, Status: MOD: WAIT TASTE
- Verifikationsmethode: Einschaltpruefung / Kaltstart-Zyklus mit Netztrennung
- Klassifizierung: Festforderung
- Prioritaet: Mittel

## so_A11: A-11
- Kategorie: Logik & Alarm
- Titel: Plausibilitaets- & Grenzwertueberwachung
- Spezifikation: Erkennung und optische Signalisierung unplausibler Signalspruenge (>= 70%) im Vergleich zum vorhergehenden Messwert.
- Zielwert / Akzeptanzkriterium: Optischer Alarm DEV: +xx.x% [ALARM] bei |Delta_rel| >= 70.0%; Nullpunktschwelle |Delta| >= 50 Digits bei Referenzwert < 10 Digits
- Verifikationsmethode: Sprungantwort-Test mit Spannungssprung am Poti
- Klassifizierung: Festforderung
- Prioritaet: Hoch

## so_A12: A-12
- Kategorie: Logik & Alarm
- Titel: Alarm-Ruecksetzung & Quittierung
- Spezifikation: Der optische Alarmzustand bleibt solange aktiv, bis ein neuer Messwert innerhalb des zulaessigen Toleranzbereichs (< 70%) per Taster bestaetigt wird.
- Zielwert / Akzeptanzkriterium: Ruecksetzung des Alarmstatus auf [OK] bei nachfolgendem Messwert im Nennbereich
- Verifikationsmethode: Stufentest mit Rueckkehr in den Toleranzbereich
- Klassifizierung: Festforderung
- Prioritaet: Hoch

## so_A13: A-13
- Kategorie: Datenspeicher
- Titel: Messwert- & Referenzwertpufferung
- Spezifikation: Unterbrechungsfreie Vorhaltung von aktuellem Messwert, vorhergehendem Referenzwert und Filterhistorie zur Laufzeit.
- Zielwert / Akzeptanzkriterium: Verzoegerungsfreie Bereitstellung aller Operanden im Arbeitsspeicher fuer die Plausibilitaetsberechnung
- Verifikationsmethode: Code-Review & Verifikation des deterministischen Speicherverhaltens
- Klassifizierung: Festforderung
- Prioritaet: Hoch

## so_A14: A-14
- Kategorie: Elektrik & Schutz
- Titel: Betriebsspannung & Signalintegritaet
- Spezifikation: Sichere Funktion bei Nennspannung +5.0V DC mit Schutz gegen offene/schwebende Eingangspotenziale.
- Zielwert / Akzeptanzkriterium: Spannungsbereich +5.0V +- 5%, definierte High-Pegel an allen Schalteingaengen im Ruhezustand
- Verifikationsmethode: DMM-Spannungsmessung & Verifikationspruefung offener Pins
- Klassifizierung: Festforderung
- Prioritaet: Hoch

## so_A15: A-15
- Kategorie: Umgebungsbed.
- Titel: Betriebsumgebung & Laborbetrieb
- Spezifikation: Zuerlaessiger Betrieb unter Standard-Labor- und Schulungsbedingungen.
- Zielwert / Akzeptanzkriterium: Umgebungstemperatur +10 C .. +40 C, relative Feuchte 20% .. 80% (nicht kondensierend), IP20
- Verifikationsmethode: Sicht- und Funktionspruefung unter Laborbedingungen
- Klassifizierung: Festforderung
- Prioritaet: Niedrig
